#usage "<b>Normalize All Schematic R/C/L Part Values</b> - v1.04 (5/18/09)<p>"
       "This ULP generates a script to normalize all resistor and cap part values. "
       "Resistors are normalized in '1K00' or '1.00K' type format. Resistor values "
       "in the form of 100 or 1.10 are normalized to 100R or 1.10R format.<p>"
       "Capacitors are normalized in '1N1' or '1.1N' type format. Likewise, any "
       "cap unit suffixs are normalized to 'uF', 'pF' or 'nF' format. Inductors "
       "may also be normalized in 'nH', 'uH' or 'mH' format."
       "<p>"
       "<author>http://www.bobstarr.net</author>";

//////////////////////////////////////////////////////////////////////////////
//
// NORMALIZE ALL R/C/L PART VALUES
//
// Copyright (C) 2009, Robert E. Starr (http://www.bobstarr.net)
// 
// REVISION HISTORY:
//
// v1.00 - 05/14/2009 (RES) - Initial Release
//
// v1.01 - 05/14/2009 (RES) - Added support for inductor values.
//
// v1.02 - 05/14/2009 (RES) - Added force upper case for other value fields.
//
// v1.03 - 05/15/2009 (RES) - Added support for EU or US value styles.
//
// v1.04 - 05/18/2009 (RES) - Added assign default values to empty value parts.
//
//////////////////////////////////////////////////////////////////////////////
//
// THIS PROGRAM IS PROVIDED AS IS AND WITHOUT WARRANTY OF ANY KIND,
// EXPRESSED OR IMPLIED.
//
//////////////////////////////////////////////////////////////////////////////

string Version = "1.04";

string fileName;

int fScriptExec = 0;    // execute script automatically after generating

int fModeR = 1;         // normalize resistors if non-zero
int fModeC = 1;         // normalize capacitors if non-zero
int fModeL = 1;         // normalize inductors if non-zero
int fUCase = 0;         // force all other parts values to uppercase
int fStyle = 0;         // 0=US, 1=Euro style

int fTrimC = 0;         // 1= truncate 'pF' or 'nF' styles to 'p' or 'n'
int fTrimL = 0;         // 1= truncate 'nH' or 'uH' styles to 'n' or 'u'

int fDefValR = 1;       // if true, set empty value R parts to default value
int fDefValC = 1;       // if true, set empty value C parts to default value
int fDefValL = 1;       // if true, set empty value L parts to default value

string strDefValueR = "(TBD)";
string strDefValueC = "(TBD)";
string strDefValueL = "(TBD)";

//////////////////////////////////////////////////////////////////////////////
// Normalize RESISTOR ('R' prefix) value field

int normalizeRValue(UL_PART part)
{
    int     i;
    int     ch;
    int     len;
    int     pos;
    int     cnt;
    int     update;
    int     flag;
    int     alldigits;
    string  val;
    string  extra;

    string  partValue = strupr(part.value);
    string  partName  = strupr(part.name);

    update = 0;

    // Normalize RESISTOR value
    // sanity checks 

    if (partName[0] != 'R' || !isdigit(partName[1]))
        return 0;

    if ((len = strlen(partValue)) <= 0)
    {
        if (fDefValR) 
        {
            // Assign default if part value is emtpy
            printf("# Set RESISTOR '%s' DEFAULT '%s'\n", part.name, strDefValueR);
            printf("VALUE %s '%s';\n\n", part.name, strDefValueR);
            return 1;
        }
        return 0;
    }

    // Get resistor value less any text after digits or R, K or M modifier
    // So, given a value of "1.00K/1W" or "1.00K 1W", val would contain "1.00K".

    cnt = 0;

    for (i=0; i < len; i++)
    {
        ch = partValue[i];

        if ((ch != '.') && !isdigit(ch) &&
            (ch != 'R') && (ch != 'K') && (ch != 'M'))
        {
            extra = strsub(partValue, i, len - i);
            break;
        }

        val = val + partValue[i];

        ++cnt;
    }

    if (cnt)
    { 
        char mod;

        len = strlen(val);

        alldigits = 1;

        for (i=0; i < len; i++)
        {
            if (!isdigit(val[i]) && (val[i] != '.'))
            {
                alldigits = 0;
                break;
            }
        }

        // If value contains all digits append an 'R" (eg 100 becomes 100R)

        if (alldigits)
        {
            if (fStyle)
            {
                flag = 0;

                // scan for any decimal point
                for (i=0; i < len; i++)
                {
                    if (val[i] == '.')
                    {
                        flag = 1;
                        val[i] = 'R';
                        break;
                    }
                }

                if (flag)
                {
                    // normlize to '47R5' type format
                    partValue = val;
                    partValue += extra;
                }
                else
                {
                    // normlize to '100R' type format
                    partValue = val +"R";
                    partValue += extra;
                }
            }
            else
            {
                // normlize to '100R' or '47R5' format
                partValue = val +"R";
                partValue += extra;
            }
            update = 1;
        }
        else
        {
            // Normalize resistor format to 1.00K, 1.00M, etc format.

            flag = 0;

            if (fStyle)
            {
                // EU STYLE: normlize to '1K00' format

                ch = val[len-1];

                if (ch == 'R' || ch == 'K' || ch == 'M')
                {
                    mod = val[len-1];

                    for (i=0; i < len; i++)
                    {
                        if (val[i] == '.')
                        {
                            val[i] = mod;
                            flag = 1;
                        }
                    }
          
                    if (flag)
                        val = strsub(val, 0, len-1);

                    partValue = val + extra;
          
                    update = 1;
                }
            }
            else
            {
                // US STYLE: normlize to '1.00K' format

                ch = val[len-1];

                if (ch != 'R' && ch != 'K' && ch != 'M')
                {
                    for (i=0; i < len; i++)
                    {
                        ch = val[i];

                        if (ch == 'R' || ch == 'K' || ch == 'M')
                        {
                            mod = val[i];
                            val[i] = '.';
                            flag = 1;
                        }
                    }
  
                    if (flag)
                        val += mod;

                    partValue = val + extra;
  
                    update = 1;
                }
            }
        }
    }

    // force any value prefixed with '.' to '0.' (eg '.1R' becomes '0.1R')

    if ((len > 0) && (partValue[0] == '.'))
    {
        string tmp = partValue;
        partValue = "0" + tmp;
        update = 1;
    }

    if (update) 
    {
        if (part.value != partValue)
        {
            printf("# Normalize RESISTOR '%s' from '%s' to '%s'\n", part.name, part.value, partValue);
            printf("VALUE %s '%s';\n\n", part.name, partValue);
        }
        else
        {
            update = 0;
        }
    }

    return update;
}

//////////////////////////////////////////////////////////////////////////////
// Normalize CAPACITOR ('C' prefix) value field

int normalizeCValue(UL_PART part)
{
    int     i;
    int     len;
    int     pos;
    int     cnt;
    int     update;
    int     flag;
    int     ch;
    string  val;
    string  extra;

    string  partValue = strupr(part.value);
    string  partName  = strupr(part.name);

    update = 0;

    // Normalize CAPACITOR value
    // sanity checks 

    if (partName[0] != 'C' || !isdigit(partName[1]))
        return 0;

    if ((len = strlen(partValue)) <= 0)
    {
        if (fDefValC) 
        {
            // Assign default if part value is emtpy
            printf("# Set CAPACITOR '%s' DEFAULT '%s'\n", part.name, strDefValueC);
            printf("VALUE %s '%s';\n\n", part.name, strDefValueC);
            return 1;
        }
        return 0;
    }

    // Fixup any value suffix pair as mF, uF, pF or nF

    if (!fTrimC)
    {
        // printf("# DEBUG name='%s' value='%s'\n", part.name, partValue);

        // no trim, force 'pf' to'pF' etc..

        if ((pos = strstr(partValue, "MF")) >= 0)
        {
            partValue[pos]   = 'm';
            partValue[pos+1] = 'F';
            update = 1;
        }
        else if ((pos = strstr(partValue, "UF")) >= 0)
        {
            partValue[pos]   = 'u';
            partValue[pos+1] = 'F';
            update = 1;
        }
        else if ((pos = strstr(partValue, "PF")) >= 0)
        {
            partValue[pos]   = 'p';
            partValue[pos+1] = 'F';
            update = 1;
        }
        else if ((pos = strstr(partValue, "NF")) >= 0)
        {
            partValue[pos]   = 'n';
            partValue[pos+1] = 'F';
            update = 1;
        }
    }
    else
    {
        // trim 'pF' to 'p'
        //      'nF' to 'n'

        val = partValue;
        
        if ((pos = strstr(val, "PF")) >= 0)
        {
            val[pos] = 'p';
            partValue = strsub(val, 0, pos+1) + strsub(val, pos+2);
        }
        else if ((pos = strstr(val, "NF")) >= 0)
        {
            val[pos] = 'n';
            partValue = strsub(val, 0, pos+1) + strsub(val, pos+2);
        }

        // recalc the length as we may have truncated the 'F' above...

        len = strlen(partValue);
    }

    if (len > 0 && !update)
    {
        // Get value less any text after digits or N, U, P or M modifier

        cnt = 0;
        val = "";

        for (i=0; i < len; i++)
        {
            ch = toupper(partValue[i]);
            
            if (!isdigit(ch) &&
                (ch != '.') && 
                (ch != 'N') && (ch != 'U') && 
                (ch != 'P') && (ch != 'M'))
            {
                extra = strsub(partValue, i, len - i);
                break;
            }

            val = val + partValue[i];

            ++cnt;
        }

        if (cnt)
        {
            char mod;

            // Normalize cap format to 4.7p, 4p7, etc format.

            flag = 0;

            if (fStyle)
            {
                // EU STYLE: normlize to '4p7' format

                ch = toupper(val[len-1]);

                if (ch == 'N' || ch == 'U' || ch == 'P' || ch == 'M')
                {
                    mod = tolower(val[len-1]);

                    for (i=0; i < len; i++)
                    {
                        if (val[i] == '.')
                        {
                            val[i] = tolower(mod);
                            flag = 1;
                        }
                    }
          
                    if (flag)
                        val = strsub(val, 0, len-1);
                    else
                        val[len-1] = tolower(val[len-1]);

                    partValue = val + extra;
          
                    update = 1;
                }
//printf("# DEBUG1 partName='%s', partValue='%s', val='%s'\n", partName, partValue, val);
//printf("# DEBUG2 val='%s', ch=%c\n", val, ch);
            }
            else
            {
                // US STYLE: normlize to '4.7p' format

                ch = toupper(val[len-1]);

                if (ch != 'N' && ch != 'U' && ch != 'P' && ch != 'M')
                {
                    for (i=0; i < len; i++)
                    {
                        ch = toupper(val[i]);

                        if (ch == 'N' || ch == 'U' || ch == 'P' || ch == 'M')
                        {
                            mod = tolower(ch);
                            val[i] = '.';
                            flag = 1;
                        }
                    }
  
                    if (flag)
                        val += mod;
                    else
                        val[len-1] = tolower(val[len-1]);

                    partValue = val + extra;
  
                    update = 1;
                }
            }
        }
    }

    // force any value prefixed with '.' to '0.' (eg '.1uF' becomes '0.1uF')

    if ((len > 0) && (partValue[0] == '.'))
    {
        string tmp = partValue;
        partValue = "0" + tmp;
        update = 1;
    }
  
    if (update) 
    {
        if (part.value != partValue)
        {
            printf("# Normalize CAPACITOR '%s' from '%s' to '%s'\n", part.name, part.value, partValue);
            printf("VALUE %s '%s';\n\n", part.name, partValue);
        }
        else
        {
            update = 0;
        }
    }

    return update;
}

//////////////////////////////////////////////////////////////////////////////
// Normalize INDUCTOR ('L' prefix) value field

int normalizeLValue(UL_PART part)
{
    int     i;
    int     len;
    int     pos;
    int     cnt;
    int     update;
    int     flag;
    int     ch;
    string  val;
    string  extra;

    string  partValue = strupr(part.value);
    string  partName  = strupr(part.name);

    update = 0;

    // Normalize INDUCTOR value
    // sanity checks 

    if (partName[0] != 'L' || !isdigit(partName[1]))
        return 0;

    if ((len = strlen(partValue)) <= 0)
    {
        if (fDefValL) 
        {
            // Assign default if part value is emtpy
            printf("# Set INDUCTOR '%s' DEFAULT '%s'\n", part.name, strDefValueL);
            printf("VALUE %s '%s';\n\n", part.name, strDefValueL);
            return 1;
        }

        return 0;
    }

    // Fixup any value suffix as nH, uH or mH

    if (!fTrimL)
    {
        // no trim, force 'pf' to'pF' etc..

        if ((pos = strstr(partValue, "NH")) >= 0)
        {
            partValue[pos]   = 'n';
            partValue[pos+1] = 'H';
            update = 1;
        }
        else if ((pos = strstr(partValue, "UH")) >= 0)
        {
            partValue[pos]   = 'u';
            partValue[pos+1] = 'H';
            update = 1;
        }
        else if ((pos = strstr(partValue, "MH")) >= 0)
        {
            partValue[pos]   = 'm';
            partValue[pos+1] = 'H';
            update = 1;
        }
    }
    else
    {
        // trim 'nH' to 'n'
        //      'uH' to 'u'
        //      'mH' to 'm'

        val = partValue;
        
        if ((pos = strstr(val, "NH")) >= 0)
        {
            val[pos] = 'n';
            partValue = strsub(val, 0, pos+1) + strsub(val, pos+2);
        }
        else if ((pos = strstr(val, "µF")) >= 0)  // FIX??
        {
            val[pos] = 'u';
            partValue = strsub(val, 0, pos+1) + strsub(val, pos+2);
        }
        else if ((pos = strstr(val, "UH")) >= 0)
        {
            val[pos] = 'u';
            partValue = strsub(val, 0, pos+1) + strsub(val, pos+2);
        }
        else if ((pos = strstr(val, "MH")) >= 0)
        {
            val[pos] = 'm';
            partValue = strsub(val, 0, pos+1) + strsub(val, pos+2);
        }

        // recalc the length as we may have truncated the 'F' above...

        len = strlen(partValue);
    }

    if (len > 0 && !update)
    {
        // Get value less any text after digits or N, U, P or M modifier

        cnt = 0;
        val = "";

        for (i=0; i < len; i++)
        {
            ch = toupper(partValue[i]);
            
            if (!isdigit(ch) && (ch != '.') && 
                (ch != 'N') && (ch != 'U') && (ch != 'H'))
            {
                extra = strsub(partValue, i, len - i);
                break;
            }

            val = val + partValue[i];

            ++cnt;
        }

        if (cnt)
        {
            char mod;

            // Normalize cap format to 4.7h, 4h7, etc format.

            flag = 0;

            if (fStyle)
            {
                // EU STYLE: normlize to '4p7' format

                ch = toupper(val[len-1]);

                if (ch == 'N' || ch == 'U' || ch == 'H')
                {
                    mod = tolower(val[len-1]);

                    for (i=0; i < len; i++)
                    {
                        if (val[i] == '.')
                        {
                            val[i] = tolower(mod);
                            flag = 1;
                        }
                    }
          
                    if (flag)
                        val = strsub(val, 0, len-1);
                    else
                        val[len-1] = tolower(val[len-1]);

                    partValue = val + extra;
          
                    update = 1;
                }
            }
            else
            {
                // US STYLE: normlize to '4.7h' format

                ch = toupper(val[len-1]);

                if (ch != 'N' && ch != 'U' && ch != 'H')
                {
                    for (i=0; i < len; i++)
                    {
                        ch = toupper(val[i]);

                        if (ch == 'N' || ch == 'U' || ch == 'H')
                        {
                            mod = tolower(ch);
                            val[i] = '.';
                            flag = 1;
                        }
                    }
  
                    if (flag)
                        val += mod;
                    else
                        val[len-1] = tolower(val[len-1]);

                    partValue = val + extra;
  
                    update = 1;
                }
            }
        }
    }

    // force any value prefixed with '.' to '0.' (eg '.1mH' becomes '0.1mH')

    if ((len > 0) && (partValue[0] == '.'))
    {
        string tmp = partValue;
        partValue = "0" + tmp;
        update = 1;
    }
  
    if (update) 
    {
        if (part.value != partValue)
        {
            printf("# Normalize INDUCTOR '%s' from '%s' to '%s'\n", part.name, part.value, partValue);
            printf("VALUE %s '%s';\n\n", part.name, partValue);
        }
        else
        {
            update = 0;
        }
    }

    return update;
}

//////////////////////////////////////////////////////////////////////////////
// Normalize Upper Case - force all other VALUE fields to upper case

int normalizeUpperCase(UL_PART part)
{
    string partValue = strupr(part.value);

    if (part.value != partValue)
    {
        printf("# Normalize UPPER CASE '%s' from '%s' to '%s'\n", part.name, part.value, partValue);
        printf("VALUE %s '%s';\n\n", part.name, partValue);
        return 1;
    }

    return 0;
}

//////////////////////////////////////////////////////////////////////////////
// Check part name for starting char followed by a digit

int IsPartNamePrefix(UL_PART part, int ch)
{
    string partName  = strupr(part.name);

    int len = strlen(partName);

    // Is this a P### format?
    if (len >= 2)
    {
        if (partName[0] == ch && isdigit(partName[1]))
            return 1;
    }

    return 0;
}

//////////////////////////////////////////////////////////////////////////////
// Script Entry Point

if (schematic)
{

    schematic(SCH)
    {
        fileName = filesetext(SCH.name, "_NormalizeRCLValues~~~.scr");

        int Result = dlgDialog("Normalize RCL Values")
        {
            string title = "Normalize R/C/L Values v" + Version;

            dlgVBoxLayout
            {
                dlgGroup(title)
                {
                    dlgCheckBox("&Normalize RESISTOR values (ie 1.00K and 100R format)", fModeR);
                    dlgCheckBox("&Normalize CAPACITOR values (ie 10uF, 10pF or 1N5 format)", fModeC);
                    dlgCheckBox("&Normalize INDUCTOR values (ie 10uH, 10nH or 10mH format)", fModeL);
                    dlgCheckBox("&Force all other part values to UPPER CASE", fUCase);
                }

                dlgGroup("Options")
                {
                    dlgGroup("Value Naming Style")
                    {
                        dlgVBoxLayout
                        {
                            dlgRadioButton("&US Style Part Values (1.00K)", fStyle);
                            dlgRadioButton("&EU Style Part Values (1K00)", fStyle);
                        }
                    }
                    dlgVBoxLayout
                    {
                        dlgGroup("Assign Defaults to Parts with Empty Values")
                        {
                            dlgHBoxLayout
                            {
                                dlgCheckBox("Assign Default R-Value", fDefValR);
                                dlgStringEdit(strDefValueR);
                            }
                            dlgHBoxLayout
                            {
                                dlgCheckBox("Assign Default C-Value", fDefValC);
                                dlgStringEdit(strDefValueC);
                            }
                            dlgHBoxLayout
                            {
                                dlgCheckBox("Assign Default L-Value", fDefValL);
                                dlgStringEdit(strDefValueL);
                            }
                        }

                        dlgCheckBox("&Trim CAP suffixes (nF->n, pF->p)", fTrimC);
                        dlgCheckBox("&Trim INDUCTOR suffixes (nH->n, uH->u, mH->m)", fTrimL);
                    }
                }
            }

            dlgHBoxLayout
            {
                dlgPushButton("OK") dlgAccept();
                dlgPushButton("-Cancel") dlgReject();
                dlgCheckBox("&Execute Script", fScriptExec);
            }
        };

        if (!Result)
            exit(0);

        output(fileName, "wtD")
        {
            printf("# 'generated by normalize-rcl-values.ulp v%s, exported from;\n", Version);
            printf("# '%s at %s;\n", SCH.name, t2string(time()));
            printf("# '%s;\n\n", EAGLE_SIGNATURE);

            SCH.sheets(S)
            {
                printf("#\n# SHEET %d - NORMALIZE PART VALUES\n#\n", S.number);
                printf("EDIT .s%d\n", S.number);

                S.parts(P)
                {
                    if (P.device.package && P.name)
                    {
                        if (IsPartNamePrefix(P, 'R'))
                        {
                            // it's a resistor prefix, normalize value
                            if (fModeR > 0)
                                normalizeRValue(P);
                        }
                        else if (IsPartNamePrefix(P, 'C'))
                        {
                            // it's a capacitor prefix, normalize value
                            if (fModeC > 0)
                                normalizeCValue(P);
                        }
                        else if (IsPartNamePrefix(P, 'L'))
                        {
                            // it's an inductor prefix, normalize value
                            if (fModeL > 0)
                                normalizeLValue(P);
                        }
                        else if (fUCase)
                        {
                            // Otherwise force all value text to upper case
                            normalizeUpperCase(P);
                        }
                    }
                }
            }

            printf("EDIT .s1\n");
        }

        if (fScriptExec)
            exit ("SCRIPT '" + fileName + "';");
        else
            exit(0);
    }
}
else
{
    dlgMessageBox("Start this ULP in Schematic!", "OK");
}

// End-Of-File
